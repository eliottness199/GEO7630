FME workspace FME_TP2.fmw

Parameters:
- SourceDataset_CSV2 = https://donnees.montreal.ca/dataset/f2d3a3ca-a15e-407c-aa12-a999bfdf5989/resource/1e67f446-ed92-4f58-9586-113fcf5b6a73/download/comptages_velos_vas.csv   # Source CSV (Comma Separated Value) File(s)
- SourceDataset_CSV2_68 = https://donnees.montreal.ca/dataset/f170fecc-18db-44bc-b4fe-5b0b6d2c7297/resource/65a37da8-a7cf-4812-a3b5-5edff31c45f6/download/comptage_velo_2023.csv   # Source CSV (Comma Separated Value) File(s)
- SourceDataset_CSV2_60 = https://donnees.montreal.ca/dataset/f170fecc-18db-44bc-b4fe-5b0b6d2c7297/resource/fd3da18e-8f87-44e4-890b-30dff05c12b8/download/comptage_velo_2022.csv   # Source CSV (Comma Separated Value) File(s)
- SourceDataset_CSV2_56 = https://donnees.montreal.ca/dataset/f170fecc-18db-44bc-b4fe-5b0b6d2c7297/resource/b463fa29-8549-4664-ae68-b17ab604e0a5/download/comptage_velo_2021.csv   # Source CSV (Comma Separated Value) File(s)
- SourceDataset_CSV2_64 = https://donnees.montreal.ca/dataset/f170fecc-18db-44bc-b4fe-5b0b6d2c7297/resource/eec17749-1a50-47b2-bc4e-1960ddc09eff/download/comptage_velo_2020.csv   # Source CSV (Comma Separated Value) File(s)
- SourceDataset_CSV2_71 = https://donnees.montreal.ca/dataset/f170fecc-18db-44bc-b4fe-5b0b6d2c7297/resource/2cd0e082-f818-4014-9390-8e1c197ba806/download/comptage_velo_2019.csv   # Source CSV (Comma Separated Value) File(s)
- SourceDataset_CSV2_58 = https://donnees.montreal.ca/dataset/f170fecc-18db-44bc-b4fe-5b0b6d2c7297/resource/eea2434f-32b3-4dc5-9035-f1642509f0e7/download/comptage_velo_2018.csv   # Source CSV (Comma Separated Value) File(s)
- SourceDataset_CSV2_62 = https://donnees.montreal.ca/dataset/f170fecc-18db-44bc-b4fe-5b0b6d2c7297/resource/c7d0546a-a218-479e-bc9f-ce8f13ca972c/download/localisation_des_compteurs_velo.csv   # Source CSV (Comma Separated Value) File(s)
- SourceDataset_CSV2_66 = https://donnees.montreal.ca/dataset/f170fecc-18db-44bc-b4fe-5b0b6d2c7297/resource/83063700-8fe7-4e6f-8c4b-ed55f4602514/download/comptagevelo2017.csv   # Source CSV (Comma Separated Value) File(s)
- SourceDataset_CSV2_70 = https://donnees.montreal.ca/dataset/f170fecc-18db-44bc-b4fe-5b0b6d2c7297/resource/6caecdd0-e5ac-48c1-a0cc-5b537936d5f6/download/comptagevelo20162.csv   # Source CSV (Comma Separated Value) File(s)
- SourceDataset_CSV2_55 = https://donnees.montreal.ca/dataset/f170fecc-18db-44bc-b4fe-5b0b6d2c7297/resource/64c26fd3-0bdf-45f8-92c6-715a9c852a7b/download/comptagevelo20152.csv   # Source CSV (Comma Separated Value) File(s)
- SourceDataset_CSV2_57 = https://donnees.montreal.ca/dataset/f170fecc-18db-44bc-b4fe-5b0b6d2c7297/resource/868b4bc8-ff55-4c48-ab3b-d80615445595/download/comptagevelo2014.csv   # Source CSV (Comma Separated Value) File(s)
- SourceDataset_CSV2_59 = https://donnees.montreal.ca/dataset/f170fecc-18db-44bc-b4fe-5b0b6d2c7297/resource/ec12447d-6b2a-45d0-b0e7-fd69c382e368/download/comptagevelo2013.csv   # Source CSV (Comma Separated Value) File(s)
- SourceDataset_CSV2_61 = https://donnees.montreal.ca/dataset/f170fecc-18db-44bc-b4fe-5b0b6d2c7297/resource/d54cec49-349e-47af-b152-7740056d7311/download/comptagevelo2012.csv   # Source CSV (Comma Separated Value) File(s)
- SourceDataset_CSV2_63 = https://donnees.montreal.ca/dataset/f170fecc-18db-44bc-b4fe-5b0b6d2c7297/resource/f2e43419-ebb2-4e38-80b6-0644c8344338/download/comptagevelo2011.csv   # Source CSV (Comma Separated Value) File(s)
- SourceDataset_CSV2_65 = https://donnees.montreal.ca/dataset/f170fecc-18db-44bc-b4fe-5b0b6d2c7297/resource/f23e1c88-cd04-467f-a64a-48f5eb1b6c9e/download/comptagevelo2010.csv   # Source CSV (Comma Separated Value) File(s)
- SourceDataset_CSV2_67 = https://donnees.montreal.ca/dataset/f170fecc-18db-44bc-b4fe-5b0b6d2c7297/resource/ee1e9541-939d-429e-919a-8ab94527773c/download/comptagevelo2009.csv   # Source CSV (Comma Separated Value) File(s)
- SourceDataset_CSV2_69 = https://donnees.montreal.ca/dataset/f170fecc-18db-44bc-b4fe-5b0b6d2c7297/resource/59ce7ec4-f398-43b5-9311-ebad77b782c3/download/comptage_velo_2024.csv   # Source CSV (Comma Separated Value) File(s)
- SourceDataset_GEOJSON = https://donnees.montreal.ca/dataset/955de068-9556-4aa1-980e-487b057bbc9d/resource/cb661499-3fa9-4793-a5fd-1ba320342fcd/download/points_mtl_trajet_2017.zip   # Source GeoJSON File or URL
- SourceDataset_GEOJSON_3 = https://donnees.montreal.ca/dataset/b628f1da-9dc3-4bb1-9875-1470f891afb1/resource/92cb062a-11be-4222-9ea5-867e7e64c5ff/download/limites-terrestres.geojson   # Source GeoJSON File or URL
- SourceDataset_SHAPEFILE = $(FME_MF_DIR)data\coordinates\coordinates.shp   # Source Esri Shapefile(s)
- SourceDataset_POSTGIS_3 = GEO7630H24   # Connection
- SourceDataset_POSTGIS = GEO7630H24   # Connection
- SourceDataset_POSTGIS_5 = GEO7630H24   # Connection
- DestDataset_POSTGIS_2 = GEO7630H24   # Connection

Readers:
- CSV2_1: CSV2 from $(SourceDataset_CSV2)
- CSV2_2: CSV2 from https://donnees.montreal.ca/dataset/f2d3a3ca-a15e-407c-aa12-a999bfdf5989/resource/69881868-2cbc-4cc0-b7cd-1a94e1985d21/download/liste_des_stations_de_comptage.csv
- CSV2_3: CSV2 from $(SourceDataset_CSV2_69)
- CSV2_4: CSV2 from $(SourceDataset_CSV2_68) in EPSG:32182
- CSV2_5: CSV2 from $(SourceDataset_CSV2_60) in EPSG:32182
- CSV2_6: CSV2 from $(SourceDataset_CSV2_56) in EPSG:32182
- CSV2_7: CSV2 from $(SourceDataset_CSV2_64) in EPSG:32182
- CSV2_8: CSV2 from $(SourceDataset_CSV2_71) in EPSG:32182
- CSV2_9: CSV2 from $(SourceDataset_CSV2_58) in EPSG:32182
- CSV2_10: CSV2 from $(SourceDataset_CSV2_62) in EPSG:32182
- CSV2_11: CSV2 from $(SourceDataset_CSV2_66) in EPSG:32182
- CSV2_12: CSV2 from $(SourceDataset_CSV2_70) in EPSG:32182
- CSV2_13: CSV2 from $(SourceDataset_CSV2_55) in EPSG:32182
- CSV2_14: CSV2 from $(SourceDataset_CSV2_57) in EPSG:32182
- CSV2_15: CSV2 from $(SourceDataset_CSV2_59) in EPSG:32182
- CSV2_16: CSV2 from $(SourceDataset_CSV2_61) in EPSG:32182
- CSV2_17: CSV2 from $(SourceDataset_CSV2_63) in EPSG:32182
- CSV2_18: CSV2 from $(SourceDataset_CSV2_65) in EPSG:32182
- CSV2_19: CSV2 from $(SourceDataset_CSV2_67) in EPSG:32182
- GEOJSON_1: GEOJSON from $(SourceDataset_GEOJSON)
- GEOJSON_2: GEOJSON from $(SourceDataset_GEOJSON_3)
- SHAPEFILE_1: SHAPEFILE from $(SourceDataset_SHAPEFILE)
- POSTGIS_1: POSTGIS from $(SourceDataset_POSTGIS)
- POSTGIS_2: POSTGIS from $(SourceDataset_POSTGIS_3)
- POSTGIS_4: POSTGIS from $(SourceDataset_POSTGIS_5)

Writers:
- POSTGIS_5: POSTGIS to $(DestDataset_POSTGIS_2)

Logger_22
    LOG_FEATURE = LOG_ONLY
    MAXCOORDS = 20
    MAXFEATS = 20
    MESSAGE = Feature is:
    SEVERITY = INFO
    LOGGED -> Logger_26
AttributeManager_55
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_17
Logger_26
    LOG_FEATURE = LOG_ONLY
    MAXCOORDS = 20
    MAXFEATS = 20
    MESSAGE = Feature is:
    SEVERITY = INFO
    LOGGED -> Logger_24
    LOGGED -> Logger_25
Logger_25
    LOG_FEATURE = LOG_ONLY
    MAXCOORDS = 20
    MAXFEATS = 20
    MESSAGE = Feature is:
    SEVERITY = INFO
    LOGGED -> Logger_24
Logger_24
    LOG_FEATURE = LOG_ONLY
    MAXCOORDS = 20
    MAXFEATS = 20
    MESSAGE = Feature is:
    SEVERITY = INFO
    LOGGED -> Logger_23
Logger_23
    LOG_FEATURE = LOG_ONLY
    MAXCOORDS = 20
    MAXFEATS = 20
    MESSAGE = Feature is:
    SEVERITY = INFO
Logger_12
    LOG_FEATURE = LOG_ONLY
    MAXCOORDS = 20
    MAXFEATS = 20
    MESSAGE = Feature is:
    SEVERITY = INFO
AttributeManager_56
    ATTR_TABLE:
      REMOVE id_station (varchar(4))
      REMOVE timestamp_local (datetime)
      REMOVE compte_dir_nord (varchar(1))
      REMOVE compte_dir_sud (varchar(1))
      REMOVE compte_dir_est (uint32)
      REMOVE compte_dir_ouest (uint32)
      RENAME_SET_VALUE compte_total > score (uint32)
      REMOVE nom_station (varchar(38))
      REMOVE nom_vas (varchar(33))
    -> AttributeManager_25
Station_2019 (reader POSTGIS_2)
    attributes: code int8, name varchar(67), latitude float8, longitude float8
    -> FeatureJoiner_28 [RIGHT]
    -> FeatureJoiner_29 [RIGHT]
Logger_21
    LOG_FEATURE = LOG_ONLY
    MAXCOORDS = 20
    MAXFEATS = 20
    MESSAGE = Feature is:
    SEVERITY = INFO
Logger_18
    LOG_FEATURE = LOG_ONLY
    MAXCOORDS = 20
    MAXFEATS = 20
    MESSAGE = Feature is:
    SEVERITY = INFO
Logger_13
    LOG_FEATURE = LOG_ONLY
    MAXCOORDS = 20
    MAXFEATS = 20
    MESSAGE = Feature is:
    SEVERITY = INFO
Logger_16
    LOG_FEATURE = LOG_ONLY
    MAXCOORDS = 20
    MAXFEATS = 20
    MESSAGE = Feature is:
    SEVERITY = INFO
Logger_15
    LOG_FEATURE = LOG_ONLY
    MAXCOORDS = 20
    MAXFEATS = 20
    MESSAGE = Feature is:
    SEVERITY = INFO
Logger_20
    LOG_FEATURE = LOG_ONLY
    MAXCOORDS = 20
    MAXFEATS = 20
    MESSAGE = Feature is:
    SEVERITY = INFO
Logger_19
    LOG_FEATURE = LOG_ONLY
    MAXCOORDS = 20
    MAXFEATS = 20
    MESSAGE = Feature is:
    SEVERITY = INFO
Logger_11
    LOG_FEATURE = LOG_ONLY
    MAXCOORDS = 20
    MAXFEATS = 20
    MESSAGE = Feature is:
    SEVERITY = INFO
Logger_17
    LOG_FEATURE = LOG_ONLY
    MAXCOORDS = 20
    MAXFEATS = 20
    MESSAGE = Feature is:
    SEVERITY = INFO
Logger_14
    LOG_FEATURE = LOG_ONLY
    MAXCOORDS = 20
    MAXFEATS = 20
    MESSAGE = Feature is:
    SEVERITY = INFO

Bookmark: Comptage vélo 2024
CSV (reader CSV2_3) [off]
    attributes: date date, heure time, id_compteur uint32, nb_passages uint32, longitude x_coordinate, latitude y_coordinate
    -> StatisticsCalculator

Bookmark: Calcul du nombre de passage par station par an
StatisticsCalculator
    ATTR_ACCUM_MODE = None
    CALCULATION_MODE = NUMERIC
    FEAT_STATS = nb_passages,NUMERIC_MODE,,,,SUM,,,,,,,,,
    GROUP_BY = latitude longitude id_compteur
    SUMMARY -> FeatureJoiner_3 [LEFT]
StatisticsCalculator_2
    ATTR_ACCUM_MODE = None
    CALCULATION_MODE = NUMERIC
    FEAT_STATS = nb_passages,NUMERIC_MODE,,,,SUM,,,,,,,,,
    GROUP_BY = latitude longitude id_compteur
    SUMMARY -> FeatureJoiner_2 [LEFT]
StatisticsCalculator_3
    ATTR_ACCUM_MODE = None
    CALCULATION_MODE = NUMERIC
    FEAT_STATS = nb_passages,NUMERIC_MODE,,,,SUM,,,,,,,,,
    GROUP_BY = latitude longitude id_compteur
    SUMMARY -> FeatureJoiner_4 [LEFT]
StatisticsCalculator_4
    ATTR_ACCUM_MODE = None
    CALCULATION_MODE = NUMERIC
    FEAT_STATS = nb_passages,NUMERIC_MODE,,,,SUM,,,,,,,,,
    GROUP_BY = latitude longitude id_compteur
    SUMMARY -> FeatureJoiner_5 [LEFT]
StatisticsCalculator_6
    ATTR_ACCUM_MODE = None
    CALCULATION_MODE = NUMERIC
    FEAT_STATS = nb_passages,NUMERIC_MODE,,,,SUM,,,,,,,,,
    GROUP_BY = latitude longitude id_compteur
    SUMMARY -> FeatureJoiner_7 [LEFT]
StatisticsCalculator_5
    ATTR_ACCUM_MODE = None
    CALCULATION_MODE = NUMERIC
    FEAT_STATS = nb_passages,NUMERIC_MODE,,,,SUM,,,,,,,,,
    GROUP_BY = latitude longitude id_compteur
    SUMMARY -> FeatureJoiner_6 [LEFT]

Bookmark: Comptage vélo 2023
CSV (reader CSV2_4)
    attributes: date date, heure time, id_compteur uint32, longitude x_coordinate, latitude y_coordinate, nb_passages uint32
    -> StatisticsCalculator_2

Bookmark: Comptage vélo 2022
CSV (reader CSV2_5)
    attributes: date date, heure time, id_compteur uint32, longitude x_coordinate, latitude y_coordinate, nb_passages uint32
    -> StatisticsCalculator_3

Bookmark: Comptage vélo 2020
CSV (reader CSV2_7)
    attributes: date date, heure time, id_compteur uint32, longitude x_coordinate, latitude y_coordinate, nb_passages uint32
    -> StatisticsCalculator_4

Bookmark: Comptage vélo 2021
CSV (reader CSV2_6)
    attributes: date date, heure time, id_compteur uint32, longitude x_coordinate, latitude y_coordinate, nb_passages uint32
    -> StatisticsCalculator_6

Bookmark: Comptage vélo 2019
CSV (reader CSV2_8)
    attributes: date date, heure time, id_compteur uint32, longitude x_coordinate, latitude y_coordinate, nb_passages uint32
    -> StatisticsCalculator_5

Bookmark: Comptage vélo 2017
CSV (reader CSV2_11) [off]
    attributes: Date varchar(11), col1 varchar(6), Berri1 uint32, Boyer uint32, Boyer 2 uint32, BrÃ©beuf uint32, Christophe-Colomb uint32, CSC (CÃ´te Sainte-Catherine) uint32, Eco-Totem - MÃ©tro Laurier uint32, Maisonneuve_2 uint32, Maisonneuve_3 uint32, Notre-Dame uint32, Parc uint32, PierDup uint32, Pont Jacques-Cartier uint32, Rachel / HÃ´tel de Ville uint32, Rachel / Papineau uint32, RenÃ©-LÃ©vesque uint32, Saint-Antoine uint32, Saint-Laurent/Bellechasse uint32, Saint-Urbain uint32
    -> StatisticsCalculator_8

Bookmark: Sommes des stations
StatisticsCalculator_8
    ATTR_ACCUM_MODE = None
    CALCULATION_MODE = NUMERIC
    FEAT_STATS = Berri1,NUMERIC_MODE,,,,SUM,,,,,,,,,;Boyer,NUMERIC_MODE,,,,SUM,,,,,,,,,;Boyer 2,NUMERIC_MODE,,,,SUM,,,,,,,,,;BrÃ©beuf,NUMERIC_MODE,,,,SUM,,,,,,,,,;Christophe-Colomb,NUMERIC_MODE,,,,SUM,,,,,,,,,;col1,NUMERIC_MODE,,,,SUM,,,,,,,,,;CSC (CÃ´te Sainte-Catherine),NUMERIC_MODE,,,,SUM,,,,,,,,,;Date,NUMERIC_MODE,,,,SUM,,,,,,,,,;Eco-Totem - MÃ©tro Laurier,NUMERIC_MODE,,,,SUM,,,,,,,,,;Maisonneuve_2,NUMERIC_MODE,,,,SUM,,,,,,,,,;Maisonneuve_3,NUMERIC_MODE,,,,SUM,,,,,,,,,;Notre-Dame,NUMERIC_MODE,,,,SUM,,,,,,,,,;Parc,NUMERIC_MODE,,,,SUM,,,,,,,,,;PierDup,NUMERIC_MODE,,,,SUM,,,,,,,,,;Pont Jacques-Cartier,NUMERIC_MODE,,,,SUM,,,,,,,,,;Rachel / HÃ´tel de Ville,NUMERIC_MODE,,,,SUM,,,,,,,,,;Rachel / Papineau,NUMERIC_MODE,,,,SUM,,,,,,,,,;RenÃ©-LÃ©vesque,NUMERIC_MODE,,,,SUM,,,,,,,,,;Saint-Antoine,NUMERIC_MODE,,,,SUM,,,,,,,,,;Saint-Laurent/Bellechasse,NUMERIC_MODE,,,,SUM,,,,,,,,,;Saint-Urbain,NUMERIC_MODE,,,,SUM,,,,,,,,,
    SUMMARY -> AttributeExploder
StatisticsCalculator_9
    ATTR_ACCUM_MODE = None
    CALCULATION_MODE = NUMERIC
    FEAT_STATS = Berri1,NUMERIC_MODE,,,,SUM,,,,,,,,,;Boyer,NUMERIC_MODE,,,,SUM,,,,,,,,,;Boyer 2,NUMERIC_MODE,,,,SUM,,,,,,,,,;BrÃ©beuf,NUMERIC_MODE,,,,SUM,,,,,,,,,;Christophe-Colomb,NUMERIC_MODE,,,,SUM,,,,,,,,,;col1,NUMERIC_MODE,,,,SUM,,,,,,,,,;CSC (CÃ´te Sainte-Catherine),NUMERIC_MODE,,,,SUM,,,,,,,,,;Date,NUMERIC_MODE,,,,SUM,,,,,,,,,;Eco-Display Parc Stanley,NUMERIC_MODE,,,,SUM,,,,,,,,,;Eco-Totem - MÃ©tro Laurier,NUMERIC_MODE,,,,SUM,,,,,,,,,;Edmond Valade,NUMERIC_MODE,,,,SUM,,,,,,,,,;Gouin / Lajeunesse,NUMERIC_MODE,,,,SUM,,,,,,,,,;Maisonneuve_2,NUMERIC_MODE,,,,SUM,,,,,,,,,;Maisonneuve_3,NUMERIC_MODE,,,,SUM,,,,,,,,,;Notre-Dame,NUMERIC_MODE,,,,SUM,,,,,,,,,;Parc,NUMERIC_MODE,,,,SUM,,,,,,,,,;PierDup,NUMERIC_MODE,,,,SUM,,,,,,,,,;Pont Jacques-Cartier,NUMERIC_MODE,,,,SUM,,,,,,,,,;Rachel / HÃ´tel de Ville,NUMERIC_MODE,,,,SUM,,,,,,,,,;Rachel / Papineau,NUMERIC_MODE,,,,SUM,,,,,,,,,;RenÃ©-LÃ©vesque,NUMERIC_MODE,,,,SUM,,,,,,,,,;Saint-Antoine,NUMERIC_MODE,,,,SUM,,,,,,,,,;Saint-Laurent/Bellechasse,NUMERIC_MODE,,,,SUM,,,,,,,,,;Saint-Urbain,NUMERIC_MODE,,,,SUM,,,,,,,,,;Viger,NUMERIC_MODE,,,,SUM,,,,,,,,,
    SUMMARY -> AttributeExploder_2
StatisticsCalculator_10
    ATTR_ACCUM_MODE = None
    CALCULATION_MODE = NUMERIC
    FEAT_STATS = Berri1,NUMERIC_MODE,,,,SUM,,,,,,,,,;Boyer,NUMERIC_MODE,,,,SUM,,,,,,,,,;BrÃ©beuf,NUMERIC_MODE,,,,SUM,,,,,,,,,;col1,NUMERIC_MODE,,,,SUM,,,,,,,,,;CSC (CÃ´te Sainte-Catherine),NUMERIC_MODE,,,,SUM,,,,,,,,,;Date,NUMERIC_MODE,,,,SUM,,,,,,,,,;Maisonneuve_2,NUMERIC_MODE,,,,SUM,,,,,,,,,;Maisonneuve_3,NUMERIC_MODE,,,,SUM,,,,,,,,,;Notre-Dame,NUMERIC_MODE,,,,SUM,,,,,,,,,;Parc,NUMERIC_MODE,,,,SUM,,,,,,,,,;PierDup,NUMERIC_MODE,,,,SUM,,,,,,,,,;Pont_Jacques_Cartier,NUMERIC_MODE,,,,SUM,,,,,,,,,;Rachel / HÃ´tel de Ville,NUMERIC_MODE,,,,SUM,,,,,,,,,;Rachel / Papineau,NUMERIC_MODE,,,,SUM,,,,,,,,,;RenÃ©-LÃ©vesque,NUMERIC_MODE,,,,SUM,,,,,,,,,;Saint-Antoine,NUMERIC_MODE,,,,SUM,,,,,,,,,;Saint-Urbain,NUMERIC_MODE,,,,SUM,,,,,,,,,;Totem_Laurier,NUMERIC_MODE,,,,SUM,,,,,,,,,;University,NUMERIC_MODE,,,,SUM,,,,,,,,,;Viger,NUMERIC_MODE,,,,SUM,,,,,,,,,
    SUMMARY -> AttributeExploder_3
StatisticsCalculator_11
    ATTR_ACCUM_MODE = None
    CALCULATION_MODE = NUMERIC
    FEAT_STATS = Berri1,NUMERIC_MODE,,,,SUM,,,,,,,,,;Boyer,NUMERIC_MODE,,,,SUM,,,,,,,,,;BrÃ©beuf,NUMERIC_MODE,,,,SUM,,,,,,,,,;col1,NUMERIC_MODE,,,,SUM,,,,,,,,,;CSC (CÃ´te Sainte-Catherine),NUMERIC_MODE,,,,SUM,,,,,,,,,;Date,NUMERIC_MODE,,,,SUM,,,,,,,,,;Maisonneuve_2,NUMERIC_MODE,,,,SUM,,,,,,,,,;Maisonneuve_3,NUMERIC_MODE,,,,SUM,,,,,,,,,;Notre-Dame,NUMERIC_MODE,,,,SUM,,,,,,,,,;Parc,NUMERIC_MODE,,,,SUM,,,,,,,,,;PierDup,NUMERIC_MODE,,,,SUM,,,,,,,,,;Pont_Jacques_Cartier,NUMERIC_MODE,,,,SUM,,,,,,,,,;Rachel / HÃ´tel de Ville,NUMERIC_MODE,,,,SUM,,,,,,,,,;Rachel / Papineau,NUMERIC_MODE,,,,SUM,,,,,,,,,;RenÃ©-LÃ©vesque,NUMERIC_MODE,,,,SUM,,,,,,,,,;Saint-Antoine,NUMERIC_MODE,,,,SUM,,,,,,,,,;Saint-Urbain,NUMERIC_MODE,,,,SUM,,,,,,,,,;Totem_Laurier,NUMERIC_MODE,,,,SUM,,,,,,,,,;University,NUMERIC_MODE,,,,SUM,,,,,,,,,;Viger,NUMERIC_MODE,,,,SUM,,,,,,,,,
    SUMMARY -> AttributeExploder_4
StatisticsCalculator_12
    ATTR_ACCUM_MODE = None
    CALCULATION_MODE = NUMERIC
    FEAT_STATS = Berri1,NUMERIC_MODE,,,,SUM,,,,,,,,,;Boyer,NUMERIC_MODE,,,,SUM,,,,,,,,,;BrÃ©beuf,NUMERIC_MODE,,,,SUM,,,,,,,,,;CSC (CÃ´te Sainte-Catherine),NUMERIC_MODE,,,,SUM,,,,,,,,,;Date,NUMERIC_MODE,,,,SUM,,,,,,,,,;Maisonneuve_1,NUMERIC_MODE,,,,SUM,,,,,,,,,;Maisonneuve_2,NUMERIC_MODE,,,,SUM,,,,,,,,,;Maisonneuve_3,NUMERIC_MODE,,,,SUM,,,,,,,,,;Notre-Dame,NUMERIC_MODE,,,,SUM,,,,,,,,,;Parc,NUMERIC_MODE,,,,SUM,,,,,,,,,;PierDup,NUMERIC_MODE,,,,SUM,,,,,,,,,;Pont_Jacques_Cartier,NUMERIC_MODE,,,,SUM,,,,,,,,,;Rachel / HÃ´tel de Ville,NUMERIC_MODE,,,,SUM,,,,,,,,,;Rachel / Papineau,NUMERIC_MODE,,,,SUM,,,,,,,,,;RenÃ©-LÃ©vesque,NUMERIC_MODE,,,,SUM,,,,,,,,,;Saint-Antoine,NUMERIC_MODE,,,,SUM,,,,,,,,,;Saint-Urbain,NUMERIC_MODE,,,,SUM,,,,,,,,,;Totem_Laurier,NUMERIC_MODE,,,,SUM,,,,,,,,,;University,NUMERIC_MODE,,,,SUM,,,,,,,,,;Viger,NUMERIC_MODE,,,,SUM,,,,,,,,,
    SUMMARY -> AttributeExploder_5
StatisticsCalculator_13
    ATTR_ACCUM_MODE = None
    CALCULATION_MODE = NUMERIC
    FEAT_STATS = Berri1,NUMERIC_MODE,,,,SUM,,,,,,,,,;Boyer,NUMERIC_MODE,,,,SUM,,,,,,,,,;BrÃ©beuf,NUMERIC_MODE,,,,SUM,,,,,,,,,;CSC (CÃ´te Sainte-Catherine),NUMERIC_MODE,,,,SUM,,,,,,,,,;Maisonneuve_1,NUMERIC_MODE,,,,SUM,,,,,,,,,;Maisonneuve_2,NUMERIC_MODE,,,,SUM,,,,,,,,,;Maisonneuve_3,NUMERIC_MODE,,,,SUM,,,,,,,,,;Notre-Dame,NUMERIC_MODE,,,,SUM,,,,,,,,,;Parc,NUMERIC_MODE,,,,SUM,,,,,,,,,;PierDup,NUMERIC_MODE,,,,SUM,,,,,,,,,;Pont_Jacques_Cartier,NUMERIC_MODE,,,,SUM,,,,,,,,,;Rachel / HÃ´tel de Ville,NUMERIC_MODE,,,,SUM,,,,,,,,,;Rachel / Papineau,NUMERIC_MODE,,,,SUM,,,,,,,,,;RenÃ©-LÃ©vesque,NUMERIC_MODE,,,,SUM,,,,,,,,,;Saint-Antoine,NUMERIC_MODE,,,,SUM,,,,,,,,,;Totem_Laurier,NUMERIC_MODE,,,,SUM,,,,,,,,,;University,NUMERIC_MODE,,,,SUM,,,,,,,,,;Viger,NUMERIC_MODE,,,,SUM,,,,,,,,,
    SUMMARY -> AttributeExploder_6
StatisticsCalculator_7
    ATTR_ACCUM_MODE = None
    CALCULATION_MODE = NUMERIC
    FEAT_STATS = Berri1,NUMERIC_MODE,,,,SUM,,,,,,,,,;BrÃ©beuf,NUMERIC_MODE,,,,SUM,,,,,,,,,;Maisonneuve_1,NUMERIC_MODE,,,,SUM,,,,,,,,,;Maisonneuve_2,NUMERIC_MODE,,,,SUM,,,,,,,,,
    SUMMARY -> AttributeExploder_7
StatisticsCalculator_14
    ATTR_ACCUM_MODE = None
    CALCULATION_MODE = NUMERIC
    FEAT_STATS = Berri1,NUMERIC_MODE,,,,SUM,,,,,,,,,;BrÃ©beuf,NUMERIC_MODE,,,,SUM,,,,,,,,,;col1,NUMERIC_MODE,,,,SUM,,,,,,,,,;CSC (CÃ´te Sainte-Catherine),NUMERIC_MODE,,,,SUM,,,,,,,,,;Date,NUMERIC_MODE,,,,,,,,,,,,,;Maisonneuve_1,NUMERIC_MODE,,,,SUM,,,,,,,,,;Maisonneuve_2,NUMERIC_MODE,,,,SUM,,,,,,,,,;Parc,NUMERIC_MODE,,,,SUM,,,,,,,,,;PierDup,NUMERIC_MODE,,,,SUM,,,,,,,,,;Pont_Jacques_Cartier,NUMERIC_MODE,,,,SUM,,,,,,,,,;Rachel / Papineau,NUMERIC_MODE,,,,SUM,,,,,,,,,
    SUMMARY -> AttributeExploder_8
StatisticsCalculator_15
    ATTR_ACCUM_MODE = None
    CALCULATION_MODE = NUMERIC
    FEAT_STATS = Berri1,NUMERIC_MODE,,,,SUM,,,,,,,,,;BrÃ©beuf,NUMERIC_MODE,,,,SUM,,,,,,,,,;col1,NUMERIC_MODE,,,,SUM,,,,,,,,,;CSC (CÃ´te Sainte-Catherine),NUMERIC_MODE,,,,SUM,,,,,,,,,;Maisonneuve_1,NUMERIC_MODE,,,,SUM,,,,,,,,,;Maisonneuve_2,NUMERIC_MODE,,,,SUM,,,,,,,,,;Parc,NUMERIC_MODE,,,,SUM,,,,,,,,,;PierDup,NUMERIC_MODE,,,,SUM,,,,,,,,,;Rachel / Papineau,NUMERIC_MODE,,,,SUM,,,,,,,,,
    SUMMARY -> AttributeExploder_9
StatisticsCalculator_16
    ATTR_ACCUM_MODE = None
    CALCULATION_MODE = NUMERIC
    FEAT_STATS = Berri1,NUMERIC_MODE,,,,SUM,,,,,,,,,;BrÃ©beuf,NUMERIC_MODE,,,,SUM,,,,,,,,,;col1,NUMERIC_MODE,,,,SUM,,,,,,,,,;CSC (CÃ´te Sainte-Catherine),NUMERIC_MODE,,,,SUM,,,,,,,,,;Maisonneuve_1,NUMERIC_MODE,,,,SUM,,,,,,,,,;Maisonneuve_2,NUMERIC_MODE,,,,SUM,,,,,,,,,;Parc,NUMERIC_MODE,,,,SUM,,,,,,,,,;PierDup,NUMERIC_MODE,,,,SUM,,,,,,,,,;Pont_Jacques_Cartier,NUMERIC_MODE,,,,SUM,,,,,,,,,;Rachel / Papineau,NUMERIC_MODE,,,,SUM,,,,,,,,,
    SUMMARY -> AttributeExploder_10

Bookmark: Inverse des colonnes
AttributeExploder
    ATTR_NAME_LABEL = _attr_name
    ATTR_VALUE_LABEL = _attr_value
    CASE = No
    EXPLODING_TYPE = Features
    KEEP_ATTRIBUTES = No
    KEEP_GEOMETRY = No
    -> AttributeManager_30
AttributeExploder_2
    ATTR_NAME_LABEL = _attr_name
    ATTR_VALUE_LABEL = _attr_value
    CASE = No
    EXPLODING_TYPE = Features
    KEEP_ATTRIBUTES = No
    KEEP_GEOMETRY = No
    -> AttributeManager_12
AttributeExploder_3
    ATTR_NAME_LABEL = _attr_name
    ATTR_VALUE_LABEL = _attr_value
    CASE = No
    EXPLODING_TYPE = Features
    KEEP_ATTRIBUTES = No
    KEEP_GEOMETRY = No
    -> AttributeManager_2
AttributeExploder_4
    ATTR_NAME_LABEL = _attr_name
    ATTR_VALUE_LABEL = _attr_value
    CASE = No
    EXPLODING_TYPE = Features
    KEEP_ATTRIBUTES = No
    KEEP_GEOMETRY = No
    -> AttributeManager_3
AttributeExploder_5
    ATTR_NAME_LABEL = _attr_name
    ATTR_VALUE_LABEL = _attr_value
    CASE = No
    EXPLODING_TYPE = Features
    KEEP_ATTRIBUTES = No
    KEEP_GEOMETRY = No
    -> AttributeManager_4
AttributeExploder_6
    ATTR_NAME_LABEL = _attr_name
    ATTR_VALUE_LABEL = _attr_value
    CASE = No
    EXPLODING_TYPE = Features
    KEEP_ATTRIBUTES = No
    KEEP_GEOMETRY = No
    -> AttributeManager_5
AttributeExploder_7
    ATTR_NAME_LABEL = _attr_name
    ATTR_VALUE_LABEL = _attr_value
    CASE = No
    EXPLODING_TYPE = Features
    KEEP_ATTRIBUTES = No
    KEEP_GEOMETRY = No
    -> AttributeManager_6
AttributeExploder_8
    ATTR_NAME_LABEL = _attr_name
    ATTR_VALUE_LABEL = _attr_value
    CASE = No
    EXPLODING_TYPE = Features
    KEEP_ATTRIBUTES = No
    KEEP_GEOMETRY = No
    -> AttributeManager_7
AttributeExploder_9
    ATTR_NAME_LABEL = _attr_name
    ATTR_VALUE_LABEL = _attr_value
    CASE = No
    EXPLODING_TYPE = Features
    KEEP_ATTRIBUTES = No
    KEEP_GEOMETRY = No
    -> AttributeManager_8
AttributeExploder_10
    ATTR_NAME_LABEL = _attr_name
    ATTR_VALUE_LABEL = _attr_value
    CASE = No
    EXPLODING_TYPE = Features
    KEEP_ATTRIBUTES = No
    KEEP_GEOMETRY = No
    -> AttributeManager_9

Bookmark: Ajout de l'ID
AttributeManager_30
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_8 [LEFT]
AttributeManager_12
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_10 [LEFT]
AttributeManager_2
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_11 [LEFT]
AttributeManager_3
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_12 [LEFT]
AttributeManager_4
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_9 [LEFT]
AttributeManager_5
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_13 [LEFT]
AttributeManager_6
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_14 [LEFT]
AttributeManager_7
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_15 [LEFT]
AttributeManager_8
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_16 [LEFT]
AttributeManager_9
    ATTR_TABLE:
      RENAME_SET_VALUE _attr_name > nom
      RENAME_SET_VALUE _attr_value > value
      SET_TO ID = FME_CONDITIONAL:DEFAULT_VALUE'_FME_NO_OP_'BOOL_OP;OR;COMPOSITE_TEST;1;TEST @Value(nom) = Berri1.sum'100003032'BOOL_OP;OR;COMPOSITE_TEST;1;TEST @Value(nom) = Boyer 2.sum'100035408
        'BOOL_OP;OR;COMPOSITE_TEST;1;TEST @Value(nom) = Boyer.sum'100012218'BOOL_OP;OR;COMPOSITE_TEST;1;TEST @Value(nom) = BrÃ©beuf.sum'100004575'BOOL_OP;OR;COMPOSITE_TEST;1;TEST @Value(nom) = CSC (CÃ´te Sainte-Catherine).sum'100003041'BOOL_OP;OR;COMPOSITE_TEST;1;TEST @Value(nom) = Christophe-Colomb.sum'100035409
        'BOOL_OP;OR;COMPOSITE_TEST;1;TEST @Value(nom) = Eco-Totem - MÃ©tro Laurier.sum'100007390'BOOL_OP;OR;COMPOSITE_TEST;1;TEST @Value(nom) = Maisonneuve_2.sum'100057500'BOOL_OP;OR;COMPOSITE_TEST;1;TEST @Value(nom) = Maisonneuve_3.sum'100003039'BOOL_OP;OR;COMPOSITE_TEST;1;TEST @Value(nom) = Notre-Dame.sum'100001753'BOOL_OP;OR;COMPOSITE_TEST;1;TEST @Value(nom) = Parc.sum'100003042'BOOL_OP;OR;COMPOSITE_TEST;1;TEST @Value(nom) = PierDup.sum'100003040'BOOL_OP;OR;COMPOSITE_TEST;1;TEST @Value(nom) = Pont Jacques-Cartier.sum'100002880'BOOL_OP;OR;COMPOSITE_TEST;1;TEST @Value(nom) = Rachel / HÃ´tel de Ville.sum'100012217'BOOL_OP;OR;COMPOSITE_TEST;1;TEST @Value(nom) = Rachel / Papineau.sum'100003034'BOOL_OP;OR;COMPOSITE_TEST;1;TEST @Value(nom) = RenÃ©-LÃ©vesque.sum'100011748'BOOL_OP;OR;COMPOSITE_TEST;1;TEST @Value(nom) = Saint-Antoine.sum'100011747'BOOL_OP;OR;COMPOSITE_TEST;1;TEST @Value(nom) = Saint-Laurent/Bellechasse.sum'100025474'BOOL_OP;OR;COMPOSITE_TEST;1;TEST @Value(nom) = Saint-Urbain.sum'100017523'BOOL_OP;OR;COMPOSITE_TEST;1;TEST @Value(nom) = Viger.sum'100047030'BOOL_OP;OR;COMPOSITE_TEST;1;TEST @Value(nom) = Eco-Display Parc Stanley.sum'100041114'BOOL_OP;OR;COMPOSITE_TEST;1;TEST @Value(nom) = Edmond Valade.sum'100041101'BOOL_OP;OR;COMPOSITE_TEST;1;TEST @Value(nom) = Gouin / Lajeunesse.sum'100034805'BOOL_OP;OR;COMPOSITE_TEST;1;TEST @Value(nom) = Pont_Jacques_Cartier.sum'100002880'BOOL_OP;OR;COMPOSITE_TEST;1;TEST @Value(nom) = Totem_Laurier.sum'100007390'BOOL_OP;OR;COMPOSITE_TEST;1;TEST @Value(nom) = University.sum'100017441'BOOL_OP;OR;COMPOSITE_TEST;1;TEST @Value(nom) = Maisonneuve_1.sum'100011783'FME_NUM_CONDITIONS28___
    USER_EXPOSED_ATTRIBUTES = ID
    -> FeatureJoiner_17 [LEFT]

Bookmark: Comptage vélo 2018
CSV (reader CSV2_9) [off]
    attributes: Date varchar(11), col1 varchar(6), Berri1 uint32, Boyer uint32, Boyer 2 uint32, BrÃ©beuf uint32, Christophe-Colomb uint32, CSC (CÃ´te Sainte-Catherine) uint32, Eco-Display Parc Stanley uint32, Eco-Totem - MÃ©tro Laurier uint32, Edmond Valade uint32, Gouin / Lajeunesse uint32, Maisonneuve_2 uint32, Maisonneuve_3 uint32, Notre-Dame uint32, Parc uint32, PierDup uint32, Pont Jacques-Cartier uint32, Rachel / HÃ´tel de Ville uint32, Rachel / Papineau uint32, RenÃ©-LÃ©vesque uint32, Saint-Antoine uint32, Saint-Laurent/Bellechasse uint32, Saint-Urbain uint32, Viger uint32
    -> StatisticsCalculator_9

Bookmark: Comptage vélo 2015
CSV (reader CSV2_13) [off]
    attributes: Date varchar(11), col1 varchar(6), Berri1 uint32, Boyer uint32, BrÃ©beuf uint32, CSC (CÃ´te Sainte-Catherine) uint32, Maisonneuve_2 uint32, Maisonneuve_3 uint32, Notre-Dame uint32, Parc uint32, PierDup uint32, Pont_Jacques_Cartier uint32, Rachel / HÃ´tel de Ville uint32, Rachel / Papineau uint32, RenÃ©-LÃ©vesque uint32, Saint-Antoine uint32, Saint-Urbain uint32, Totem_Laurier uint32, University uint32, Viger uint32
    -> StatisticsCalculator_10

Bookmark: Comptage vélo 2016
CSV (reader CSV2_12) [off]
    attributes: Date varchar(11), col1 varchar(6), Berri1 uint32, Boyer uint32, BrÃ©beuf uint32, CSC (CÃ´te Sainte-Catherine) uint32, Maisonneuve_2 uint32, Maisonneuve_3 uint32, Notre-Dame uint32, Parc uint32, PierDup uint32, Pont_Jacques_Cartier uint32, Rachel / HÃ´tel de Ville uint32, Rachel / Papineau uint32, RenÃ©-LÃ©vesque uint32, Saint-Antoine uint32, Saint-Urbain uint32, Totem_Laurier uint32, University uint32, Viger uint32
    -> StatisticsCalculator_11

Bookmark: Comptage vélo 2014
CSV (reader CSV2_14)
    attributes: Date date, Rachel / Papineau uint32, Berri1 uint32, Maisonneuve_1 uint32, Maisonneuve_2 uint32, BrÃ©beuf uint32, Parc uint32, PierDup uint32, CSC (CÃ´te Sainte-Catherine) uint32, Pont_Jacques_Cartier varchar(1), Totem_Laurier uint32, Notre-Dame uint32, Rachel / HÃ´tel de Ville uint32, Saint-Antoine uint32, RenÃ©-LÃ©vesque uint32, Viger uint32, Boyer uint32, Maisonneuve_3 uint32, University uint32, Saint-Urbain uint32
    -> StatisticsCalculator_12

Bookmark: Comptage vélo 2013
CSV (reader CSV2_15) [off]
    attributes: Date date, Rachel / Papineau uint32, Berri1 uint32, Maisonneuve_1 uint32, Maisonneuve_2 uint32, BrÃ©beuf uint32, Parc uint32, PierDup uint32, CSC (CÃ´te Sainte-Catherine) uint32, Pont_Jacques_Cartier varchar(1), Totem_Laurier uint32, Notre-Dame uint32, Rachel / HÃ´tel de Ville uint32, Saint-Antoine uint32, RenÃ©-LÃ©vesque uint32, Viger uint32, Boyer uint32, Maisonneuve_3 uint32, University uint32
    -> StatisticsCalculator_13

Bookmark: Comptage vélo 2009
CSV (reader CSV2_19)
    attributes: Date varchar(11), col1 varchar(6), Berri1 uint32, Maisonneuve_1 uint32, Maisonneuve_2 uint32, BrÃ©beuf uint32
    -> StatisticsCalculator_7

Bookmark: Comptage vélo 2011
CSV (reader CSV2_17) [off]
    attributes: Date varchar(11), col1 varchar(6), Rachel / Papineau uint32, Berri1 uint32, Maisonneuve_2 uint32, Maisonneuve_1 uint32, BrÃ©beuf uint32, Parc uint32, PierDup uint32, CSC (CÃ´te Sainte-Catherine) uint32, Pont_Jacques_Cartier uint32
    -> StatisticsCalculator_14

Bookmark: Comptage vélo 2010
CSV (reader CSV2_18)
    attributes: Date varchar(11), col1 varchar(6), Rachel / Papineau uint32, Berri1 uint32, Maisonneuve_1 uint32, Maisonneuve_2 uint32, BrÃ©beuf uint32, Parc uint32, CSC (CÃ´te Sainte-Catherine) uint32, PierDup uint32
    -> StatisticsCalculator_15

Bookmark: Comptage vélo 2012
CSV (reader CSV2_16) [off]
    attributes: Date varchar(11), col1 varchar(6), Rachel / Papineau uint32, Berri1 uint32, Maisonneuve_2 uint32, Maisonneuve_1 uint32, BrÃ©beuf uint32, Parc uint32, PierDup uint32, CSC (CÃ´te Sainte-Catherine) uint32, Pont_Jacques_Cartier uint32
    -> StatisticsCalculator_16

Bookmark: Trajet MTL
Note: 2016 ? a confirmer
coordinates (reader SHAPEFILE_1) [off]
    attributes: id_coord number(18,0), latitude double, longitude double, speed double, h_accuracy double, v_accuracy double, timestamp varchar(80), id_trip long
    -> Reprojector_4
Reprojector_4 [off]
    DEST = EPSG:3857
    INTERPOLATION_TYPE_NAME = Nearest Neighbor
    RASTER_CELL_SIZE = Preserve Cells
    RASTER_TOLERANCE = 0.0
    REPROJECTED -> Clipper_2 [CANDIDATE]
Note: 2017
points_mtl_trajet_2017-1 (reader GEOJSON_1) [off]
    attributes: latitude float, longitude float, speed float, altitude float, h_accuracy float, v_accuracy float, timestamp string, id_trip int
    -> Reprojector_2
Reprojector_2
    DEST = EPSG:3857
    INTERPOLATION_TYPE_NAME = Nearest Neighbor
    RASTER_CELL_SIZE = Preserve Cells
    RASTER_TOLERANCE = 0.0
    REPROJECTED -> Clipper [CANDIDATE]
limites-terrestres (reader GEOJSON_2) [off]
    attributes: DefaultAtt string
    -> Reprojector_3
Reprojector_3
    DEST = EPSG:3857
    INTERPOLATION_TYPE_NAME = Nearest Neighbor
    RASTER_CELL_SIZE = Preserve Cells
    RASTER_TOLERANCE = 0.0
    REPROJECTED -> Clipper [CLIPPER]
    REPROJECTED -> Clipper_2 [CLIPPER]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeManager
AttributeManager
    ATTR_TABLE:
      REMOVE speed
      REMOVE altitude
      REMOVE h_accuracy
      REMOVE v_accuracy
      REMOVE timestamp
      REMOVE id_trip
      REMOVE _clipped
      RENAME_SET_VALUE value > score = @Evaluate(1)
    USER_EXPOSED_ATTRIBUTES = value
    -> AttributeManager_22
Clipper_2 [off]
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeManager_13
Note: ??
AttributeManager_13 [off]
    ATTR_TABLE:
      REMOVE speed
      REMOVE h_accuracy
      REMOVE v_accuracy
      RENAME_SET_VALUE timestamp
      REMOVE _clipped

Bookmark: Localisation des compteurs
CSV (reader CSV2_10)
    attributes: ID uint32, Ancien_ID uint32, Nom varchar(40), Statut varchar(18), Latitude y_coordinate, Longitude x_coordinate, Annee_implante uint32
    -> FeatureJoiner_2 [RIGHT]
    -> FeatureJoiner_3 [RIGHT]
    -> FeatureJoiner_4 [RIGHT]
    -> FeatureJoiner_5 [RIGHT]
    -> FeatureJoiner_6 [RIGHT]
    -> FeatureJoiner_7 [RIGHT]
    -> AttributeManager_11
AttributeManager_11
    ATTR_TABLE:
      REMOVE Ancien_ID
      REMOVE Statut
      REMOVE Annee_implante
      SET_TO ID_2 = @Value(ID)
    USER_EXPOSED_ATTRIBUTES = ID_2
    -> FeatureJoiner_10 [RIGHT]
    -> FeatureJoiner_8 [RIGHT]
    -> FeatureJoiner_11 [RIGHT]
    -> FeatureJoiner_12 [RIGHT]
    -> FeatureJoiner_9 [RIGHT]
    -> FeatureJoiner_13 [RIGHT]
    -> FeatureJoiner_14 [RIGHT]
    -> FeatureJoiner_15 [RIGHT]
    -> FeatureJoiner_16 [RIGHT]
    -> FeatureJoiner_17 [RIGHT]

Bookmark: Jointure attributaire avec l'ID du compteur et supression des champs inutiles
FeatureJoiner_7
    ATTR_CONFLICT_RES = Prefer Left
    GEOMETRY_HANDLING = Prefer Left
    JOIN_KEYS = id_compteur ID AUTO
    JOIN_MODE = Inner
    JOINED -> AttributeRemover_6
Note: 2021
AttributeRemover_6
    REMOVE_ATTRS = Ancien_ID,Latitude,Longitude,ID
    -> AttributeManager_40
AttributeManager_40
    ATTR_TABLE:
      REMOVE id_compteur (uint32)
      RENAME_SET_VALUE nb_passages.sum > score (real64)
      REMOVE Nom (varchar(40))
      REMOVE Statut (varchar(18))
      REMOVE Annee_implante (uint32)
      SET_TO score (varchar(200)) = @Evaluate(@Value(nb_passages.sum))
    USER_EXPOSED_ATTRIBUTES = score
    -> AttributeManager_26
FeatureJoiner_5
    ATTR_CONFLICT_RES = Prefer Left
    GEOMETRY_HANDLING = Prefer Left
    JOIN_KEYS = id_compteur ID AUTO
    JOIN_MODE = Inner
    JOINED -> AttributeRemover_4
Note: 2020
AttributeRemover_4
    REMOVE_ATTRS = Ancien_ID,Latitude,Longitude,ID
    -> AttributeManager_41
AttributeManager_41
    ATTR_TABLE:
      RENAME_SET_VALUE nb_passages.sum > score (real64)
      REMOVE Nom (varchar(40))
      REMOVE Statut (varchar(18))
      REMOVE Annee_implante (uint32)
    USER_EXPOSED_ATTRIBUTES = score
    -> AttributeManager_25
FeatureJoiner_6
    ATTR_CONFLICT_RES = Prefer Left
    GEOMETRY_HANDLING = Prefer Left
    JOIN_KEYS = id_compteur ID AUTO
    JOIN_MODE = Inner
    JOINED -> AttributeRemover_5
Note: 2019
AttributeRemover_5
    REMOVE_ATTRS = Ancien_ID,Latitude,Longitude,ID
    -> AttributeManager_42
AttributeManager_42
    ATTR_TABLE = SET_TO score (varchar(200)) = @Evaluate(@Value(nb_passages.sum))
    USER_EXPOSED_ATTRIBUTES = score
    -> AttributeManager_24
FeatureJoiner_4
    ATTR_CONFLICT_RES = Prefer Left
    GEOMETRY_HANDLING = Prefer Left
    JOIN_KEYS = id_compteur ID AUTO
    JOIN_MODE = Inner
    JOINED -> AttributeRemover_3
Note: 2022
AttributeRemover_3
    REMOVE_ATTRS = Ancien_ID,Latitude,Longitude,ID
    -> AttributeManager_43
AttributeManager_43
    ATTR_TABLE:
      REMOVE id_compteur (uint32)
      RENAME_SET_VALUE nb_passages.sum > score (real64)
      REMOVE Nom (varchar(40))
      REMOVE Statut (varchar(18))
      REMOVE Annee_implante (uint32)
    USER_EXPOSED_ATTRIBUTES = score
    -> AttributeManager_27
FeatureJoiner_3
    ATTR_CONFLICT_RES = Prefer Left
    GEOMETRY_HANDLING = Prefer Left
    JOIN_KEYS = id_compteur ID AUTO
    JOIN_MODE = Inner
    JOINED -> AttributeRemover_2
Note: 2024
AttributeRemover_2
    REMOVE_ATTRS = Ancien_ID,Latitude,Longitude,ID
    -> AttributeManager_44
AttributeManager_44
    ATTR_TABLE:
      RENAME_SET_VALUE nb_passages.sum > score (real64)
      REMOVE Nom (varchar(40))
      REMOVE Statut (varchar(18))
      REMOVE Annee_implante (uint32)
    USER_EXPOSED_ATTRIBUTES = score
    -> AttributeManager_29
FeatureJoiner_2
    ATTR_CONFLICT_RES = Prefer Left
    GEOMETRY_HANDLING = Prefer Left
    JOIN_KEYS = id_compteur ID AUTO
    JOIN_MODE = Inner
    JOINED -> AttributeRemover
Note: 2023
AttributeRemover
    REMOVE_ATTRS = Ancien_ID,Latitude,Longitude,ID
    -> AttributeManager_45
AttributeManager_45
    ATTR_TABLE:
      REMOVE id_compteur (uint32)
      RENAME_SET_VALUE nb_passages.sum > score (real64)
      REMOVE Nom (varchar(40))
      REMOVE Statut (varchar(18))
      REMOVE Annee_implante (uint32)
    USER_EXPOSED_ATTRIBUTES = score
    -> AttributeManager_28

Bookmark: Joindre L'Id avec les coordonnées
Note: 2017
FeatureJoiner_8
    ATTR_CONFLICT_RES = Prefer Left
    GEOMETRY_HANDLING = Prefer Left
    JOIN_KEYS = ID ID_2 AUTO
    JOIN_MODE = Inner
    JOINED -> AttributeManager_46
    <REJECTED> -> Logger
AttributeManager_46
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_22
Note: 2018
AttributeManager_47
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
      REMOVE score (buffer)
    USER_EXPOSED_ATTRIBUTES = score
    -> AttributeManager_23
Note: 2015
FeatureJoiner_11
    ATTR_CONFLICT_RES = Prefer Left
    GEOMETRY_HANDLING = Prefer Left
    JOIN_KEYS = ID ID_2 AUTO
    JOIN_MODE = Inner
    JOINED -> AttributeManager_48
    <REJECTED> -> Logger_4
AttributeManager_48
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_20
Note: 2016
FeatureJoiner_12
    ATTR_CONFLICT_RES = Prefer Left
    GEOMETRY_HANDLING = Prefer Left
    JOIN_KEYS = ID ID_2 AUTO
    JOIN_MODE = Inner
    JOINED -> AttributeManager_49
    <REJECTED> -> Logger_10
AttributeManager_49
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_21
Note: 2014
FeatureJoiner_9
    ATTR_CONFLICT_RES = Prefer Left
    GEOMETRY_HANDLING = Prefer Left
    JOIN_KEYS = ID ID AUTO
    JOIN_MODE = Inner
    JOINED -> AttributeManager_50
    <REJECTED> -> Logger_2
AttributeManager_50
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
      REMOVE score (buffer)
    USER_EXPOSED_ATTRIBUTES = score
    -> AttributeManager_19
Note: 2013
FeatureJoiner_13
    ATTR_CONFLICT_RES = Prefer Left
    GEOMETRY_HANDLING = Prefer Left
    JOIN_KEYS = ID ID_2 AUTO
    JOIN_MODE = Inner
    JOINED -> AttributeManager_51
    <REJECTED> -> Logger_6
AttributeManager_51
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
      REMOVE score (buffer)
    USER_EXPOSED_ATTRIBUTES = score
    -> AttributeManager_18
Note: 2009
FeatureJoiner_14
    ATTR_CONFLICT_RES = Prefer Left
    GEOMETRY_HANDLING = Prefer Left
    JOIN_KEYS = ID ID_2 AUTO
    JOIN_MODE = Inner
    JOINED -> AttributeManager_52
    <REJECTED> -> Logger_6
AttributeManager_52
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_14
Note: 2011
FeatureJoiner_15
    ATTR_CONFLICT_RES = Prefer Left
    GEOMETRY_HANDLING = Prefer Left
    JOIN_KEYS = ID ID_2 AUTO
    JOIN_MODE = Inner
    JOINED -> AttributeManager_53
    <REJECTED> -> Logger_7
AttributeManager_53
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_16
Note: 2010
FeatureJoiner_16
    ATTR_CONFLICT_RES = Prefer Left
    GEOMETRY_HANDLING = Prefer Left
    JOIN_KEYS = ID ID_2 AUTO
    JOIN_MODE = Inner
    JOINED -> AttributeManager_54
    <REJECTED> -> Logger_8
Note: 2012
FeatureJoiner_17
    ATTR_CONFLICT_RES = Prefer Left
    GEOMETRY_HANDLING = Prefer Left
    JOIN_KEYS = ID ID_2 AUTO
    JOIN_MODE = Inner
    JOINED -> AttributeManager_55
    <REJECTED> -> Logger_10

Bookmark: LLots de ogger
Logger
    LOG_FEATURE = LOG_ONLY
    MAXCOORDS = 20
    MAXFEATS = 20
    MESSAGE = Feature is:
    SEVERITY = INFO
Logger_3
    LOG_FEATURE = LOG_ONLY
    MAXCOORDS = 20
    MAXFEATS = 20
    MESSAGE = Feature is:
    SEVERITY = INFO
Logger_4
    LOG_FEATURE = LOG_ONLY
    MAXCOORDS = 20
    MAXFEATS = 20
    MESSAGE = Feature is:
    SEVERITY = INFO
Logger_2
    LOG_FEATURE = LOG_ONLY
    MAXCOORDS = 20
    MAXFEATS = 20
    MESSAGE = Feature is:
    SEVERITY = INFO
Logger_6
    LOG_FEATURE = LOG_ONLY
    MAXCOORDS = 20
    MAXFEATS = 20
    MESSAGE = Feature is:
    SEVERITY = INFO
    LOGGED -> Logger_7
Logger_7
    LOG_FEATURE = LOG_ONLY
    MAXCOORDS = 20
    MAXFEATS = 20
    MESSAGE = Feature is:
    SEVERITY = INFO
    LOGGED -> Logger_5
Logger_5
    LOG_FEATURE = LOG_ONLY
    MAXCOORDS = 20
    MAXFEATS = 20
    MESSAGE = Feature is:
    SEVERITY = INFO
Logger_8
    LOG_FEATURE = LOG_ONLY
    MAXCOORDS = 20
    MAXFEATS = 20
    MESSAGE = Feature is:
    SEVERITY = INFO
Logger_10
    LOG_FEATURE = LOG_ONLY
    MAXCOORDS = 20
    MAXFEATS = 20
    MESSAGE = Feature is:
    SEVERITY = INFO
    LOGGED -> Logger_9
Logger_9
    LOG_FEATURE = LOG_ONLY
    MAXCOORDS = 20
    MAXFEATS = 20
    MESSAGE = Feature is:
    SEVERITY = INFO

Bookmark: Station de comptage
FeatureJoiner_10
    ATTR_CONFLICT_RES = Prefer Left
    GEOMETRY_HANDLING = Prefer Left
    JOIN_KEYS = ID ID_2 AUTO
    JOIN_MODE = Inner
    JOINED -> AttributeManager_47
    <REJECTED> -> Logger_3
AttributeManager_54
    ATTR_TABLE:
      REMOVE nom (buffer)
      RENAME_SET_VALUE value > score (buffer)
      REMOVE ID (varchar(200))
      REMOVE Nom (varchar(40))
      RENAME_SET_VALUE Latitude > latitude (real64)
      RENAME_SET_VALUE Longitude > longitude (real64)
      REMOVE ID_2 (varchar(200))
    USER_EXPOSED_ATTRIBUTES = score
    -> AttributeManager_15

Bookmark: Compilation + création d'un point
Note: 2013
AttributeManager_18
    -> VertexCreator_5
VertexCreator_5
    CLOSE_LINES = Yes
    IGNORE_DUPLICATES = No
    MEASURE_TYPE = Continuous
    MISSING_VAL_MODE = Compute
    MODE_NAME = Add Point
    XVAL = @Value(longitude)
    YVAL = @Value(latitude)
    -> Reprojector_9
    <REJECTED> -> Logger_22
Note: 2009
AttributeManager_14
    -> VertexCreator
VertexCreator
    CLOSE_LINES = Yes
    IGNORE_DUPLICATES = No
    MEASURE_TYPE = Continuous
    MISSING_VAL_MODE = Compute
    MODE_NAME = Add Point
    XVAL = @Value(longitude)
    YVAL = @Value(latitude)
    -> Reprojector_22
    <REJECTED> -> Logger_25
Note: 2011
AttributeManager_16
    -> VertexCreator_3
VertexCreator_3
    CLOSE_LINES = Yes
    IGNORE_DUPLICATES = No
    MEASURE_TYPE = Continuous
    MISSING_VAL_MODE = Compute
    MODE_NAME = Add Point
    XVAL = @Value(longitude)
    YVAL = @Value(latitude)
    -> Reprojector_7
    <REJECTED> -> Logger_25
Note: 2010
AttributeManager_15
    -> VertexCreator_2
VertexCreator_2
    CLOSE_LINES = Yes
    IGNORE_DUPLICATES = No
    MEASURE_TYPE = Continuous
    MISSING_VAL_MODE = Compute
    MODE_NAME = Add Point
    XVAL = @Value(longitude)
    YVAL = @Value(latitude)
    -> Reprojector_6
    <REJECTED> -> Logger_22
Note: 2012
AttributeManager_17
    -> VertexCreator_4
VertexCreator_4
    CLOSE_LINES = Yes
    IGNORE_DUPLICATES = No
    MEASURE_TYPE = Continuous
    MISSING_VAL_MODE = Compute
    MODE_NAME = Add Point
    XVAL = @Value(longitude)
    YVAL = @Value(latitude)
    -> Reprojector_8
    <REJECTED> -> Logger_26
Note: 2024
AttributeManager_29
    -> AttributeManager_82
Note: score en int64
AttributeManager_82
    -> VertexCreator_16
VertexCreator_16
    CLOSE_LINES = Yes
    IGNORE_DUPLICATES = No
    MEASURE_TYPE = Continuous
    MISSING_VAL_MODE = Compute
    MODE_NAME = Add Point
    XVAL = @Value(longitude)
    YVAL = @Value(latitude)
    -> Reprojector_20
    <REJECTED> -> Logger_12
Note: 2014
AttributeManager_19
    -> VertexCreator_6
VertexCreator_6
    CLOSE_LINES = Yes
    IGNORE_DUPLICATES = No
    MEASURE_TYPE = Continuous
    MISSING_VAL_MODE = Compute
    MODE_NAME = Add Point
    XVAL = @Value(longitude)
    YVAL = @Value(latitude)
    -> Reprojector_10
    <REJECTED> -> Logger_21
Note: 2017
AttributeManager_22
    -> VertexCreator_9
VertexCreator_9
    CLOSE_LINES = Yes
    IGNORE_DUPLICATES = No
    MEASURE_TYPE = Continuous
    MISSING_VAL_MODE = Compute
    MODE_NAME = Add Point
    XVAL = @Value(longitude)
    YVAL = @Value(latitude)
    -> Reprojector_13
    <REJECTED> -> Logger_18
Note: 2022
AttributeManager_27
    -> AttributeManager_80
Note: score en int64
AttributeManager_80
    -> VertexCreator_14
VertexCreator_14
    CLOSE_LINES = Yes
    IGNORE_DUPLICATES = No
    MEASURE_TYPE = Continuous
    MISSING_VAL_MODE = Compute
    MODE_NAME = Add Point
    XVAL = @Value(longitude)
    YVAL = @Value(latitude)
    -> Reprojector_18
    <REJECTED> -> Logger_13
Note: 2019
AttributeManager_24
    ATTR_TABLE = SET_TO (number(20,10))
    USER_EXPOSED_ATTRIBUTES = score
    -> AttributeManager_77
Note: score en int64
AttributeManager_77
    -> VertexCreator_11
VertexCreator_11
    CLOSE_LINES = Yes
    IGNORE_DUPLICATES = No
    MEASURE_TYPE = Continuous
    MISSING_VAL_MODE = Compute
    MODE_NAME = Add Point
    XVAL = @Value(longitude)
    YVAL = @Value(latitude)
    -> Reprojector_15
    <REJECTED> -> Logger_16
Note: 2020
AttributeManager_25
    -> AttributeManager_78
Note: score en int64
AttributeManager_78
    -> VertexCreator_12
VertexCreator_12
    CLOSE_LINES = Yes
    IGNORE_DUPLICATES = No
    MEASURE_TYPE = Continuous
    MISSING_VAL_MODE = Compute
    MODE_NAME = Add Point
    XVAL = @Value(longitude)
    YVAL = @Value(latitude)
    -> Reprojector_16
    <REJECTED> -> Logger_15
Note: 2015
AttributeManager_20
    -> VertexCreator_7
VertexCreator_7
    CLOSE_LINES = Yes
    IGNORE_DUPLICATES = No
    MEASURE_TYPE = Continuous
    MISSING_VAL_MODE = Compute
    MODE_NAME = Add Point
    XVAL = @Value(longitude)
    YVAL = @Value(latitude)
    -> Reprojector_11
    <REJECTED> -> Logger_20
Note: 2016
AttributeManager_21
    -> VertexCreator_8
VertexCreator_8
    CLOSE_LINES = Yes
    IGNORE_DUPLICATES = No
    MEASURE_TYPE = Continuous
    MISSING_VAL_MODE = Compute
    MODE_NAME = Add Point
    XVAL = @Value(longitude)
    YVAL = @Value(latitude)
    -> Reprojector_12
    <REJECTED> -> Logger_19
Note: 2023
AttributeManager_28
    -> AttributeManager_81
Note: score en int64
AttributeManager_81
    -> VertexCreator_15
VertexCreator_15
    CLOSE_LINES = Yes
    IGNORE_DUPLICATES = No
    MEASURE_TYPE = Continuous
    MISSING_VAL_MODE = Compute
    MODE_NAME = Add Point
    XVAL = @Value(longitude)
    YVAL = @Value(latitude)
    -> Reprojector_19
    <REJECTED> -> Logger_11
Note: 2018
AttributeManager_23
    -> VertexCreator_10
VertexCreator_10
    CLOSE_LINES = Yes
    IGNORE_DUPLICATES = No
    MEASURE_TYPE = Continuous
    MISSING_VAL_MODE = Compute
    MODE_NAME = Add Point
    XVAL = @Value(longitude)
    YVAL = @Value(latitude)
    -> Reprojector_14
    <REJECTED> -> Logger_17
Note: 2021
AttributeManager_26
    -> AttributeManager_79
Note: score en int64
AttributeManager_79
    -> VertexCreator_13
VertexCreator_13
    CLOSE_LINES = Yes
    IGNORE_DUPLICATES = No
    MEASURE_TYPE = Continuous
    MISSING_VAL_MODE = Compute
    MODE_NAME = Add Point
    XVAL = @Value(longitude)
    YVAL = @Value(latitude)
    -> Reprojector_17
    <REJECTED> -> Logger_14

Bookmark: Reprojection 4326 to 3857
Reprojector_9
    DEST = EPSG:3857
    INTERPOLATION_TYPE_NAME = Nearest Neighbor
    RASTER_CELL_SIZE = Preserve Cells
    RASTER_TOLERANCE = 0.0
    SOURCE = EPSG:4326
    REPROJECTED -> Point_2013 (writer POSTGIS_5)
Reprojector_22
    DEST = EPSG:3857
    INTERPOLATION_TYPE_NAME = Nearest Neighbor
    RASTER_CELL_SIZE = Preserve Cells
    RASTER_TOLERANCE = 0.0
    SOURCE = EPSG:4326
    REPROJECTED -> Point_2009 (writer POSTGIS_5)
Reprojector_7
    DEST = EPSG:3857
    INTERPOLATION_TYPE_NAME = Nearest Neighbor
    RASTER_CELL_SIZE = Preserve Cells
    RASTER_TOLERANCE = 0.0
    SOURCE = EPSG:4326
    REPROJECTED -> Point_2011 (writer POSTGIS_5)
Reprojector_6
    DEST = EPSG:3857
    INTERPOLATION_TYPE_NAME = Nearest Neighbor
    RASTER_CELL_SIZE = Preserve Cells
    RASTER_TOLERANCE = 0.0
    SOURCE = EPSG:4326
    REPROJECTED -> Point_2010 (writer POSTGIS_5)
Reprojector_8
    DEST = EPSG:3857
    INTERPOLATION_TYPE_NAME = Nearest Neighbor
    RASTER_CELL_SIZE = Preserve Cells
    RASTER_TOLERANCE = 0.0
    SOURCE = EPSG:4326
    REPROJECTED -> Point_2012 (writer POSTGIS_5)
Reprojector_20
    DEST = EPSG:3857
    INTERPOLATION_TYPE_NAME = Nearest Neighbor
    RASTER_CELL_SIZE = Preserve Cells
    RASTER_TOLERANCE = 0.0
    SOURCE = EPSG:4326
    REPROJECTED -> Point_2024 (writer POSTGIS_5)
Reprojector_10
    DEST = EPSG:3857
    INTERPOLATION_TYPE_NAME = Nearest Neighbor
    RASTER_CELL_SIZE = Preserve Cells
    RASTER_TOLERANCE = 0.0
    SOURCE = EPSG:4326
    REPROJECTED -> Point_2014 (writer POSTGIS_5)
Reprojector_13
    DEST = EPSG:3857
    INTERPOLATION_TYPE_NAME = Nearest Neighbor
    RASTER_CELL_SIZE = Preserve Cells
    RASTER_TOLERANCE = 0.0
    SOURCE = EPSG:4326
    REPROJECTED -> Point_2017 (writer POSTGIS_5)
Reprojector_18
    DEST = EPSG:3857
    INTERPOLATION_TYPE_NAME = Nearest Neighbor
    RASTER_CELL_SIZE = Preserve Cells
    RASTER_TOLERANCE = 0.0
    SOURCE = EPSG:4326
    REPROJECTED -> Point_2022 (writer POSTGIS_5)
Reprojector_15
    DEST = EPSG:3857
    INTERPOLATION_TYPE_NAME = Nearest Neighbor
    RASTER_CELL_SIZE = Preserve Cells
    RASTER_TOLERANCE = 0.0
    SOURCE = EPSG:4326
    REPROJECTED -> Point_2019 (writer POSTGIS_5)
Reprojector_16
    DEST = EPSG:3857
    INTERPOLATION_TYPE_NAME = Nearest Neighbor
    RASTER_CELL_SIZE = Preserve Cells
    RASTER_TOLERANCE = 0.0
    SOURCE = EPSG:4326
    REPROJECTED -> Point_2020 (writer POSTGIS_5)
Reprojector_11
    DEST = EPSG:3857
    INTERPOLATION_TYPE_NAME = Nearest Neighbor
    RASTER_CELL_SIZE = Preserve Cells
    RASTER_TOLERANCE = 0.0
    SOURCE = EPSG:4326
    REPROJECTED -> Point_2015 (writer POSTGIS_5)
Reprojector_12
    DEST = EPSG:3857
    INTERPOLATION_TYPE_NAME = Nearest Neighbor
    RASTER_CELL_SIZE = Preserve Cells
    RASTER_TOLERANCE = 0.0
    SOURCE = EPSG:4326
    REPROJECTED -> Point_2016 (writer POSTGIS_5)
Reprojector_19
    DEST = EPSG:3857
    INTERPOLATION_TYPE_NAME = Nearest Neighbor
    RASTER_CELL_SIZE = Preserve Cells
    RASTER_TOLERANCE = 0.0
    SOURCE = EPSG:4326
    REPROJECTED -> Point_2023 (writer POSTGIS_5)
Reprojector_14
    DEST = EPSG:3857
    INTERPOLATION_TYPE_NAME = Nearest Neighbor
    RASTER_CELL_SIZE = Preserve Cells
    RASTER_TOLERANCE = 0.0
    SOURCE = EPSG:4326
    REPROJECTED -> Point_2018 (writer POSTGIS_5)
Reprojector_17
    DEST = EPSG:3857
    INTERPOLATION_TYPE_NAME = Nearest Neighbor
    RASTER_CELL_SIZE = Preserve Cells
    RASTER_TOLERANCE = 0.0
    SOURCE = EPSG:4326
    REPROJECTED -> Point_2021 (writer POSTGIS_5)

Bookmark: Write dans la BD
Point_2013 (writer POSTGIS_5) [off]
    attributes: longitude float8, latitude float8, score int8
Point_2009 (writer POSTGIS_5) [off]
    attributes: longitude float8, latitude float8, score int8
Point_2011 (writer POSTGIS_5) [off]
    attributes: longitude float8, latitude float8, score int8
Point_2010 (writer POSTGIS_5) [off]
    attributes: longitude float8, latitude float8, score int8
Point_2012 (writer POSTGIS_5) [off]
    attributes: longitude float8, latitude float8, score int8
Point_2024 (writer POSTGIS_5) [off]
    attributes: longitude float8, latitude float8, score int8
Point_2014 (writer POSTGIS_5)
    attributes: longitude float8, latitude float8, score int8
Point_2017 (writer POSTGIS_5) [off]
    attributes: longitude float8, latitude float8, score int8
Point_2022 (writer POSTGIS_5)
    attributes: longitude float8, latitude float8, score int8
Point_2019 (writer POSTGIS_5)
    attributes: longitude float8, latitude float8, score int8
Point_2020 (writer POSTGIS_5)
    attributes: longitude float8, latitude float8, score int8
Point_2015 (writer POSTGIS_5) [off]
    attributes: longitude float8, latitude float8, score int8
Point_2016 (writer POSTGIS_5) [off]
    attributes: longitude float8, latitude float8, score int8
Point_2023 (writer POSTGIS_5)
    attributes: longitude float8, latitude float8, score int8
Point_2018 (writer POSTGIS_5) [off]
    attributes: longitude float8, latitude float8, score int8
Point_2021 (writer POSTGIS_5)
    attributes: longitude float8, latitude float8, score int8

Bookmark: Voie sécuritaire vélos
Note: Données 2020
CSV (reader CSV2_1)
    attributes: id_station varchar(4), timestamp_local datetime, compte_dir_nord varchar(1), compte_dir_sud varchar(1), compte_dir_est uint32, compte_dir_ouest uint32, compte_total uint32
    -> Reprojector
Reprojector
    DEST = EPSG:3857
    INTERPOLATION_TYPE_NAME = Nearest Neighbor
    RASTER_CELL_SIZE = Preserve Cells
    RASTER_TOLERANCE = 0.0
    REPROJECTED -> FeatureJoiner [LEFT]
Note: Infos
CSV (reader CSV2_2)
    attributes: id_station varchar(4), nom_station varchar(38), nom_vas varchar(33), latitude y_coordinate, longitude x_coordinate
    -> FeatureJoiner [RIGHT]
Note: 2020
FeatureJoiner
    ATTR_CONFLICT_RES = Prefer Left
    GEOMETRY_HANDLING = Prefer Left
    JOIN_KEYS = id_station id_station AUTO
    JOIN_MODE = Inner
    JOINED -> AttributeManager_56

Bookmark: Bixi
Station_2014 (reader POSTGIS_4)
    attributes: code int8, name varchar(52), latitude float8, longitude float8
    -> FeatureJoiner_19 [RIGHT]
    -> FeatureJoiner_18 [RIGHT]
Station_2017 (reader POSTGIS_2) [off]
    attributes: code int8, name varchar(62), latitude float8, longitude float8
    -> FeatureJoiner_24 [RIGHT]
    -> FeatureJoiner_25 [RIGHT]
Station_2020 (reader POSTGIS_2)
    attributes: code int8, name varchar(77), latitude float8, longitude float8
    -> FeatureJoiner_30 [RIGHT]
    -> FeatureJoiner_31 [RIGHT]
Station_2018 (reader POSTGIS_2) [off]
    attributes: code int8, name varchar(64), latitude float8, longitude float8
    -> FeatureJoiner_26 [RIGHT]
    -> FeatureJoiner_27 [RIGHT]
Station_2015 (reader POSTGIS_1) [off]
    attributes: code int8, name varchar(52), latitude float8, longitude float8
    -> FeatureJoiner_20 [RIGHT]
    -> FeatureJoiner_21 [RIGHT]
Station_2021 (reader POSTGIS_2)
    attributes: pk int8, name varchar(74), latitude float8, longitude float8
    -> FeatureJoiner_32 [RIGHT]
    -> FeatureJoiner_33 [RIGHT]

Bookmark: Déplacements BIXI 2014
BIXI_2014 (reader POSTGIS_2)
    attributes: start_date varchar(16), start_station_code int8, end_date varchar(16), end_station_code int8, duration_sec int8, is_member int8
    -> End_station
    -> Start_station

Bookmark: Dissocie les points de départ et les points d'arrivée
Start_station: AttributeRemover
    REMOVE_ATTRS = duration_sec,end_date,end_station_code,is_member
    -> FeatureJoiner_18 [LEFT]
End_station: AttributeRemover
    REMOVE_ATTRS = duration_sec,is_member,start_date,start_station_code
    -> FeatureJoiner_19 [LEFT]

Bookmark: Jointure des points de départ (ID) avec le nom et les coordonnées des stations
FeatureJoiner_18
    ATTR_CONFLICT_RES = Prefer Left
    GEOMETRY_HANDLING = Prefer Left
    JOIN_KEYS = start_station_code code AUTO
    JOIN_MODE = Inner
    JOINED -> AttributeManager_67
FeatureJoiner_19
    ATTR_CONFLICT_RES = Prefer Left
    GEOMETRY_HANDLING = Prefer Left
    JOIN_KEYS = end_station_code code AUTO
    JOIN_MODE = Inner
    JOINED -> AttributeManager_57

Bookmark: 2014
AttributeManager_67
    ATTR_TABLE:
      REMOVE start_date (varchar(16))
      REMOVE start_station_code (int64)
      REMOVE code (int64)
      REMOVE name (varchar(52))
      SET_TO score (varchar(200)) = @Evaluate(1)
    USER_EXPOSED_ATTRIBUTES = score
    -> AttributeManager_19
AttributeManager_57
    ATTR_TABLE:
      REMOVE end_date (varchar(16))
      REMOVE end_station_code (int64)
      REMOVE name (varchar(52))
      REMOVE code (int64)
      SET_TO score (uint64) = @Evaluate(1)
    USER_EXPOSED_ATTRIBUTES = end_date.total_count,score
    -> AttributeManager_19

Bookmark: Déplacements BIXI 2017
BIXI_2017 (reader POSTGIS_2) [off]
    attributes: start_date varchar(16), start_station_code int8, end_date varchar(16), end_station_code int8, duration_sec int8, is_member int8
    -> Start_station_4
    -> End_station_4

Bookmark: Dissocie les points de départ et les points d'arrivée
Start_station_4: AttributeRemover
    REMOVE_ATTRS = duration_sec,end_date,end_station_code,is_member
    -> FeatureJoiner_24 [LEFT]
End_station_4: AttributeRemover
    REMOVE_ATTRS = duration_sec,is_member,start_date,start_station_code
    -> FeatureJoiner_25 [LEFT]

Bookmark: Jointure des points de départ (ID) avec le nom et les coordonnées des stations
FeatureJoiner_24
    ATTR_CONFLICT_RES = Prefer Left
    GEOMETRY_HANDLING = Prefer Left
    JOIN_KEYS = start_station_code code AUTO
    JOIN_MODE = Inner
    JOINED -> AttributeManager_69
FeatureJoiner_25
    ATTR_CONFLICT_RES = Prefer Left
    GEOMETRY_HANDLING = Prefer Left
    JOIN_KEYS = end_station_code code AUTO
    JOIN_MODE = Inner
    JOINED -> AttributeManager_59

Bookmark: 2017
AttributeManager_69
    ATTR_TABLE:
      REMOVE start_date (varchar(16))
      REMOVE start_station_code (int64)
      REMOVE code (int64)
      REMOVE name (varchar(62))
      SET_TO score (varchar(200)) = @Evaluate(1)
    USER_EXPOSED_ATTRIBUTES = score
    -> AttributeManager_22
AttributeManager_59
    ATTR_TABLE:
      REMOVE end_date (varchar(16))
      REMOVE end_station_code (int64)
      REMOVE name (varchar(62))
      REMOVE code (int64)
      SET_TO score (varchar(200)) = @Evaluate(1)
    USER_EXPOSED_ATTRIBUTES = score
    -> AttributeManager_22

Bookmark: 2022
BIXI_2022 (reader POSTGIS_2)
    attributes: startstationname varchar(67), startstationarrondissement varchar(43), startstationlatitude float8, startstationlongitude float8, endstationname varchar(67), endstationarrondissement varchar(43), endstationlatitude float8, endstationlongitude float8, starttimems numeric(20,0), endtimems numeric(20,0)
    -> Reprojector_5
Reprojector_5
    DEST = EPSG:2950
    INTERPOLATION_TYPE_NAME = Nearest Neighbor
    RASTER_CELL_SIZE = Preserve Cells
    RASTER_TOLERANCE = 0.0
    REPROJECTED -> Start_station_9
    REPROJECTED -> End_station_9
AttributeManager_65
    ATTR_TABLE:
      RENAME_SET_VALUE (uint64)
      REMOVE startstationname (varchar(67))
      REMOVE startstationarrondissement (varchar(43))
      RENAME_SET_VALUE startstationlatitude > latitude (real64)
      RENAME_SET_VALUE startstationlongitude > longitude (real64)
      REMOVE starttimems (number(20,0))
      SET_TO score (varchar(200)) = @Evaluate(1)
    USER_EXPOSED_ATTRIBUTES = score
    -> AttributeManager_27
AttributeManager_76
    ATTR_TABLE:
      REMOVE endstationname (varchar(67))
      REMOVE endstationarrondissement (varchar(43))
      RENAME_SET_VALUE endstationlatitude > latitude (real64)
      RENAME_SET_VALUE endstationlongitude > longitude (real64)
      SET_TO score (uint64) = @Evaluate(1)
      SET_TO
    USER_EXPOSED_ATTRIBUTES = score
    -> AttributeManager_27

Bookmark: Dissocie les points de départ et les points d'arrivée
Start_station_9: AttributeRemover
    REMOVE_ATTRS = endstationarrondissement,endstationlatitude,endstationlongitude,endstationname,endtimems
    -> AttributeManager_65
End_station_9: AttributeRemover
    REMOVE_ATTRS = startstationarrondissement,startstationlatitude,startstationlongitude,startstationname,starttimems
    -> AttributeManager_76

Bookmark: Déplacements BIXI 2019
BIXI_2019 (reader POSTGIS_2)
    attributes: start_date varchar(16), start_station_code int8, end_date varchar(16), end_station_code int8, duration_sec int8, is_member int8
    -> Start_station_6
    -> End_station_6

Bookmark: Dissocie les points de départ et les points d'arrivée
Start_station_6: AttributeRemover
    REMOVE_ATTRS = duration_sec,end_date,end_station_code,is_member
    -> FeatureJoiner_28 [LEFT]
End_station_6: AttributeRemover
    REMOVE_ATTRS = duration_sec,is_member,start_date,start_station_code
    -> FeatureJoiner_29 [LEFT]

Bookmark: Jointure des points de départ (ID) avec le nom et les coordonnées des stations
FeatureJoiner_28
    ATTR_CONFLICT_RES = Prefer Left
    GEOMETRY_HANDLING = Prefer Left
    JOIN_KEYS = start_station_code code AUTO
    JOIN_MODE = Inner
    JOINED -> AttributeManager_71
    UNJOINED_LEFT -> FeatureJoiner_11__Rejected_
    <REJECTED> -> FeatureJoiner_11__Rejected_
FeatureJoiner_29
    ATTR_CONFLICT_RES = Prefer Left
    GEOMETRY_HANDLING = Prefer Left
    JOIN_KEYS = end_station_code code AUTO
    JOIN_MODE = Inner
    JOINED -> AttributeManager_61
    UNJOINED_LEFT -> FeatureJoiner_12__Rejected_
    <REJECTED> -> FeatureJoiner_12__Rejected_

Bookmark: 2019
AttributeManager_71
    ATTR_TABLE:
      REMOVE start_date (varchar(16))
      REMOVE start_station_code (int64)
      REMOVE code (int64)
      REMOVE name (varchar(67))
      SET_TO score (varchar(200)) = @Evaluate(1)
    USER_EXPOSED_ATTRIBUTES = score
    -> AttributeManager_24
FeatureJoiner_11__Rejected_: Logger
    LOG_FEATURE = LOG_ONLY
    MAXCOORDS = 20
    MAXFEATS = 20
    MESSAGE = Feature is:
    SEVERITY = INFO
AttributeManager_61
    ATTR_TABLE:
      REMOVE end_date (varchar(16))
      REMOVE end_station_code (int64)
      REMOVE name (varchar(67))
      REMOVE code (int64)
      SET_TO score (uint64) = @Evaluate(1)
    USER_EXPOSED_ATTRIBUTES = score
    -> AttributeManager_24
FeatureJoiner_12__Rejected_: Logger
    LOG_FEATURE = LOG_ONLY
    MAXCOORDS = 20
    MAXFEATS = 20
    MESSAGE = Feature is:
    SEVERITY = INFO

Bookmark: Déplacements BIXI 2020
BIXI_2020 (reader POSTGIS_2)
    attributes: start_date varchar(16), start_station_code int8, end_date varchar(16), end_station_code int8, duration_sec int8, is_member int8
    -> End_station_7
    -> Start_station_7

Bookmark: Dissocie les points de départ et les points d'arrivée
Start_station_7: AttributeRemover
    REMOVE_ATTRS = duration_sec,end_date,end_station_code,is_member
    -> FeatureJoiner_30 [LEFT]
End_station_7: AttributeRemover
    REMOVE_ATTRS = duration_sec,is_member,start_date,start_station_code
    -> FeatureJoiner_31 [LEFT]

Bookmark: Jointure des points de départ (ID) avec le nom et les coordonnées des stations
FeatureJoiner_30
    ATTR_CONFLICT_RES = Prefer Left
    GEOMETRY_HANDLING = Prefer Left
    JOIN_KEYS = start_station_code code AUTO
    JOIN_MODE = Inner
    JOINED -> AttributeManager_64
    UNJOINED_LEFT -> FeatureJoiner_11__Rejected__2
    <REJECTED> -> FeatureJoiner_11__Rejected__2
FeatureJoiner_31
    ATTR_CONFLICT_RES = Prefer Left
    GEOMETRY_HANDLING = Prefer Left
    JOIN_KEYS = end_station_code code AUTO
    JOIN_MODE = Inner
    JOINED -> AttributeManager_63
    UNJOINED_LEFT -> FeatureJoiner_12__Rejected__2
    <REJECTED> -> FeatureJoiner_12__Rejected__2

Bookmark: 2020
AttributeManager_64
    ATTR_TABLE:
      REMOVE start_date (varchar(16))
      REMOVE start_station_code (int64)
      REMOVE code (int64)
      REMOVE name (varchar(77))
      REMOVE start_date.total_count (number(20,10))
      SET_TO score (varchar(200)) = @Evaluate(1)
    USER_EXPOSED_ATTRIBUTES = score
    -> AttributeManager_25
FeatureJoiner_11__Rejected__2: Logger
    LOG_FEATURE = LOG_ONLY
    MAXCOORDS = 20
    MAXFEATS = 20
    MESSAGE = Feature is:
    SEVERITY = INFO
AttributeManager_63
    ATTR_TABLE:
      REMOVE end_date (varchar(16))
      REMOVE end_station_code (int64)
      REMOVE name (varchar(77))
      RENAME_SET_VALUE (uint64)
      REMOVE code (int64)
      SET_TO score (varchar(200)) = @Evaluate(1)
    USER_EXPOSED_ATTRIBUTES = score
    -> AttributeManager_25
FeatureJoiner_12__Rejected__2: Logger
    LOG_FEATURE = LOG_ONLY
    MAXCOORDS = 20
    MAXFEATS = 20
    MESSAGE = Feature is:
    SEVERITY = INFO

Bookmark: Déplacements BIXI 2015
BIXI_2015 (reader POSTGIS_1) [off]
    attributes: start_date varchar(16), start_station_code int8, end_date varchar(16), end_station_code int8, duration_sec int8, is_member int8
    -> Start_station_2
    -> End_station_2

Bookmark: Dissocie les points de départ et les points d'arrivée
Start_station_2: AttributeRemover
    REMOVE_ATTRS = duration_sec,end_date,end_station_code,is_member
    -> FeatureJoiner_20 [LEFT]
End_station_2: AttributeRemover
    REMOVE_ATTRS = duration_sec,is_member,start_date,start_station_code
    -> FeatureJoiner_21 [LEFT]

Bookmark: Jointure des points de départ (ID) avec le nom et les coordonnées des stations
FeatureJoiner_20
    ATTR_CONFLICT_RES = Prefer Left
    GEOMETRY_HANDLING = Prefer Left
    JOIN_KEYS = start_station_code code AUTO
    JOIN_MODE = Inner
    JOINED -> AttributeManager_68
FeatureJoiner_21
    ATTR_CONFLICT_RES = Prefer Left
    GEOMETRY_HANDLING = Prefer Left
    JOIN_KEYS = end_station_code code AUTO
    JOIN_MODE = Inner
    JOINED -> AttributeManager_58

Bookmark: 2015
AttributeManager_68
    ATTR_TABLE:
      REMOVE start_date (varchar(16))
      REMOVE start_station_code (int64)
      REMOVE code (int64)
      REMOVE name (varchar(52))
      SET_TO score (varchar(200)) = @Evaluate(1)
    USER_EXPOSED_ATTRIBUTES = score
    -> AttributeManager_20
AttributeManager_58
    ATTR_TABLE:
      REMOVE end_date (varchar(16))
      REMOVE end_station_code (int64)
      REMOVE name (varchar(52))
      REMOVE code (int64)
      SET_TO score (uint64) = @Evaluate(1)
    USER_EXPOSED_ATTRIBUTES = end_date.total_count,score
    -> AttributeManager_20

Bookmark: Stations BIXI 2016
Station_2016 (reader POSTGIS_2) [off]
    attributes: code int8, name varchar(52), latitude float8, longitude float8
    -> FeatureJoiner_23 [RIGHT]
    -> FeatureJoiner_22 [RIGHT]

Bookmark: Déplacements BIXI 2016
BIXI_2016 (reader POSTGIS_2) [off]
    attributes: start_date varchar(16), start_station_code int8, end_date varchar(16), end_station_code int8, duration_sec int8, is_member int8
    -> End_station_3
    -> Start_station_3

Bookmark: Dissocie les points de départ et les points d'arrivée
Start_station_3: AttributeRemover
    REMOVE_ATTRS = duration_sec,end_date,end_station_code,is_member
    -> FeatureJoiner_22 [LEFT]
End_station_3: AttributeRemover
    REMOVE_ATTRS = duration_sec,is_member,start_date,start_station_code
    -> FeatureJoiner_23 [LEFT]

Bookmark: Jointure des points de départ (ID) avec le nom et les coordonnées des stations
FeatureJoiner_22
    ATTR_CONFLICT_RES = Prefer Left
    GEOMETRY_HANDLING = Prefer Left
    JOIN_KEYS = start_station_code code AUTO
    JOIN_MODE = Inner
    JOINED -> AttributeManager_70
FeatureJoiner_23
    ATTR_CONFLICT_RES = Prefer Left
    GEOMETRY_HANDLING = Prefer Left
    JOIN_KEYS = end_station_code code AUTO
    JOIN_MODE = Inner
    JOINED -> AttributeManager_60

Bookmark: 2016
AttributeManager_70
    ATTR_TABLE:
      REMOVE start_date (varchar(16))
      REMOVE start_station_code (int64)
      REMOVE code (int64)
      REMOVE name (varchar(52))
      SET_TO score (varchar(200)) = @Evaluate(1)
    USER_EXPOSED_ATTRIBUTES = score
    -> AttributeManager_21
AttributeManager_60
    ATTR_TABLE:
      REMOVE end_date (varchar(16))
      REMOVE end_station_code (int64)
      REMOVE name (varchar(52))
      REMOVE code (int64)
      SET_TO score (uint64) = @Evaluate(1)
    USER_EXPOSED_ATTRIBUTES = score
    -> AttributeManager_21

Bookmark: Déplacements BIXI 2023
BIXI_2023 (reader POSTGIS_2)
    attributes: startstationname varchar(67), startstationarrondissement varchar(43), startstationlatitude float8, startstationlongitude float8, endstationname varchar(67), endstationarrondissement varchar(43), endstationlatitude float8, endstationlongitude float8, starttimems numeric(20,0), endtimems numeric(20,0)
    -> End_station_10
    -> Start_station_10

Bookmark: Dissocie les points de départ et les points d'arrivée
Start_station_10: AttributeRemover
    REMOVE_ATTRS = endstationarrondissement,endstationlatitude,endstationlongitude,endstationname,endtimems
    -> AttributeManager_84
End_station_10: AttributeRemover
    REMOVE_ATTRS = startstationarrondissement,startstationlatitude,startstationlongitude,startstationname,starttimems
    -> AttributeManager_83

Bookmark: 2023
AttributeManager_84
    ATTR_TABLE:
      SET_TO score (varchar(200)) = @Evaluate(1)
      REMOVE startstationname (varchar(67))
      REMOVE startstationarrondissement (varchar(43))
      RENAME_SET_VALUE startstationlatitude > latitude (real64)
      RENAME_SET_VALUE startstationlongitude > longitude (real64)
      REMOVE starttimems (number(20,0))
    USER_EXPOSED_ATTRIBUTES = score
    -> AttributeManager_28
AttributeManager_83
    ATTR_TABLE:
      REMOVE endstationname (varchar(67))
      REMOVE endstationarrondissement (varchar(43))
      RENAME_SET_VALUE endstationlatitude > latitude (real64)
      RENAME_SET_VALUE endstationlongitude > longitude (real64)
      REMOVE endtimems (number(20,0))
      SET_TO score (varchar(200)) = @Evaluate(1)
    USER_EXPOSED_ATTRIBUTES = score
    -> AttributeManager_28

Bookmark: Déplacements BIXI 2018
BIXI_2018 (reader POSTGIS_2) [off]
    attributes: start_date varchar(16), start_station_code int8, end_date varchar(16), end_station_code int8, duration_sec int8, is_member int8
    -> Start_station_5
    -> End_station_5

Bookmark: Dissocie les points de départ et les points d'arrivée
Start_station_5: AttributeRemover
    REMOVE_ATTRS = duration_sec,end_date,end_station_code,is_member
    -> FeatureJoiner_26 [LEFT]
End_station_5: AttributeRemover
    REMOVE_ATTRS = duration_sec,is_member,start_date,start_station_code
    -> FeatureJoiner_27 [LEFT]

Bookmark: Jointure des points de départ (ID) avec le nom et les coordonnées des stations
FeatureJoiner_26
    ATTR_CONFLICT_RES = Prefer Left
    GEOMETRY_HANDLING = Prefer Left
    JOIN_KEYS = start_station_code code AUTO
    JOIN_MODE = Inner
    JOINED -> AttributeManager_72
FeatureJoiner_27
    ATTR_CONFLICT_RES = Prefer Left
    GEOMETRY_HANDLING = Prefer Left
    JOIN_KEYS = end_station_code code AUTO
    JOIN_MODE = Inner
    JOINED -> AttributeManager_62

Bookmark: 2018
AttributeManager_72
    ATTR_TABLE:
      REMOVE start_date (varchar(16))
      REMOVE start_station_code (int64)
      REMOVE code (int64)
      REMOVE name (varchar(64))
      SET_TO score (varchar(200)) = @Evaluate(1)
      SET_TO
    USER_EXPOSED_ATTRIBUTES = score
    -> AttributeManager_23
AttributeManager_62
    ATTR_TABLE:
      REMOVE end_date (varchar(16))
      REMOVE end_station_code (int64)
      REMOVE name (varchar(64))
      REMOVE code (int64)
      SET_TO score (uint64) = @Evaluate(1)
    USER_EXPOSED_ATTRIBUTES = end_date.total_count,score
    -> AttributeManager_23

Bookmark: Déplacements BIXI 2021
BIXI_2021 (reader POSTGIS_2)
    attributes: start_date timestamp, emplacement_pk_start int8, end_date timestamp, emplacement_pk_end int8, duration_sec int8, is_member int8
    -> End_station_8
    -> Start_station_8

Bookmark: Dissocie les points de départ et les points d'arrivée
Start_station_8: AttributeRemover
    REMOVE_ATTRS = duration_sec,end_date,is_member,emplacement_pk_end
    -> FeatureJoiner_32 [LEFT]
End_station_8: AttributeRemover
    REMOVE_ATTRS = duration_sec,is_member,start_date,emplacement_pk_start
    -> FeatureJoiner_33 [LEFT]

Bookmark: Jointure des points de départ (ID) avec le nom et les coordonnées des stations
FeatureJoiner_32
    ATTR_CONFLICT_RES = Prefer Left
    GEOMETRY_HANDLING = Prefer Left
    JOIN_KEYS = emplacement_pk_start pk AUTO
    JOIN_MODE = Inner
    JOINED -> AttributeManager_73
    UNJOINED_LEFT -> FeatureJoiner_11__Rejected__3
    <REJECTED> -> FeatureJoiner_11__Rejected__3
FeatureJoiner_33
    ATTR_CONFLICT_RES = Prefer Left
    GEOMETRY_HANDLING = Prefer Left
    JOIN_KEYS = emplacement_pk_end pk AUTO
    JOIN_MODE = Inner
    JOINED -> AttributeManager_74
    UNJOINED_LEFT -> FeatureJoiner_12__Rejected__3
    <REJECTED> -> FeatureJoiner_12__Rejected__3

Bookmark: 2021
AttributeManager_73
    ATTR_TABLE:
      REMOVE start_date (datetime)
      REMOVE name (varchar(74))
      REMOVE start_date.total_count (number(20,10))
      REMOVE emplacement_pk_start (int64)
      REMOVE pk (int64)
      SET_TO score (varchar(200)) = @Evaluate(1)
    USER_EXPOSED_ATTRIBUTES = score
    -> AttributeManager_26
FeatureJoiner_11__Rejected__3: Logger
    LOG_FEATURE = LOG_ONLY
    MAXCOORDS = 20
    MAXFEATS = 20
    MESSAGE = Feature is:
    SEVERITY = INFO
AttributeManager_74
    ATTR_TABLE:
      REMOVE end_date (datetime)
      REMOVE emplacement_pk_end (int64)
      REMOVE end_date.total_count (number(20,10))
      REMOVE pk (int64)
      SET_TO score (varchar(200)) = @Evaluate(1)
    USER_EXPOSED_ATTRIBUTES = score
    -> AttributeManager_26
FeatureJoiner_12__Rejected__3: Logger
    LOG_FEATURE = LOG_ONLY
    MAXCOORDS = 20
    MAXFEATS = 20
    MESSAGE = Feature is:
    SEVERITY = INFO
